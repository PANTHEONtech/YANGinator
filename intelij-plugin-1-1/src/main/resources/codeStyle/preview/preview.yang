/* The preview may not display changes correctly, but it works correctly. */
module acme-foo {
  namespace "http://acme.example.com/foo";
  prefix "acfoo";

  //aaa
  import my-extensions{
    prefix "myext";
  }
  list interface {
    key "name";
    leaf name {
      type string;
    }
  }
}
