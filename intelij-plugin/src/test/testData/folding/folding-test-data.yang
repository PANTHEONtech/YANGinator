<fold text='/*...*/'>/*
 *
 *   Copyright (c) 2021 PANTHEON.tech, s.r.o. All rights reserved.
 *
 *   This program and the accompanying materials are made available under the
 *   terms of the Eclipse Public License v1.0 which accompanies this distribution,
 *   and is available at http://www.eclipse.org/legal/epl-v10.html
 *
 */</fold>

module module-name <fold text='{ ... }'>{
    yang-version 1;
    namespace <fold text='"..."'>"namespace"</fold>;
    prefix <fold text='"..."'>"prefix"</fold>;

    description
        <fold text='"..."'>"This file should have functioning folding
        descriptors because all curly braces and quotation marks
        are paired. These braces should be ignored: }}}}}{{"</fold>;          //Also there: }}}}}{{ "
<fold text='/*...*/'>/*
This should be ok too: }}}}}{{ ""
*/</fold>
    revision <fold text='"..."'>"2021-09-22"</fold> <fold text='{ ... }'>{
            description
            <fold text='"..."'>"Just another description"</fold>;
    }</fold>

    typedef another-type <fold text='{ ... }'>{
                type string;
                description
                    <fold text='"..."'>"Just another description"</fold>;
                reference
                    <fold text='"..."'>"Just another reference"</fold>;
    }</fold>

    grouping another-model <fold text='{ ... }'>{
        leaf name <fold text='{ ... }'>{
            description <fold text='"..."'>"Just another description"</fold>;
            type string;

        }</fold>
        leaf version <fold text='{ ... }'>{
            description
                <fold text='"..."'>"Lorem ipsum dolor sit amet, consectetur adipiscing elit,
                sed do eiusmod tempor incididunt ut labore et dolore magna aliqua. Ut
                enim ad minim veniam, quis nostrud exercitation ullamco laboris nisi ut
                aliquip ex ea commodo consequat. Duis aute irure dolor in reprehenderit"</fold>;
            type another-type2;
        }</fold>
    }</fold>
}</fold>
