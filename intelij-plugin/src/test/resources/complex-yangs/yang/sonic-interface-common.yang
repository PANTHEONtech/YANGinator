module sonic-interface-common {
    namespace "http://github.com/Azure/sonic-interface-common";
    prefix "sint-cmn";

    organization
        "SONiC";

    contact
        "SONiC";

    description
        "SONIC INTERFACE COMMON";

    revision 2020-04-06 {
        description
            "Initial revision";
    }

    typedef vrf-ip {
        type string {
            pattern '((Vrf[a-zA-Z0-9_-]+\|)|)((([0-9]|[1-9][0-9]|1[0-9]{2}|2[0-4][0-9]|25[0-5])\.){3}([0-9]|[1-9][0-9]|1[0-9]{2}|2[0-4][0-9]|25[0-5]))';
        }
        description
            "Type definition representing a host that is a combination of optional Vrf and IP address.
            Examples:
            192.168.1.2
            Vrf-RED|192.168.1.1";
    }

}
