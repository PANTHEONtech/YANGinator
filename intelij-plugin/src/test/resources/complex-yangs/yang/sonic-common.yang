module sonic-common {
    namespace "http://github.com/Azure/sonic-common";
    prefix scommon;

    organization
        "SONiC";

    contact
        "SONiC";

    description
        "SONIC Common";

    revision 2020-08-04 {
        description
            "Added fec-mode type.";
    }

    revision 2019-05-15 {
        description
            "Initial revision.";
    }

    typedef tagging_mode {
        type enumeration {
            enum untagged;
            enum tagged;
            enum priority_tagged;
        }
    }

    typedef admin-status {
        type enumeration {
            enum up;
            enum down;
        }
    }

    typedef oper-status {
        type enumeration {
            enum up;
            enum down;
        }
    }

    typedef mode-enable {
          type enumeration {
              enum enable;
              enum disable;
          }
      }

    typedef fec-mode {
          type enumeration {
              enum rs;
              enum fc;
              enum none;
          }
      }

     typedef relay-policy-action {
          type enumeration {
              enum discard;
              enum append;
              enum replace;
            }
    }

    typedef percentage {
        type uint8 {
            range "0..100";
        }
        description
            "Integer indicating a percentage value";
    }

    container operation {
        leaf operation {
            type enumeration {
                enum CREATE;
                enum UPDATE;
                enum DELETE;
            }
        }
    }
}
