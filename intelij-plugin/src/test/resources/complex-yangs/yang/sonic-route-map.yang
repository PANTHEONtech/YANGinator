module sonic-route-map {
    namespace "http://github.com/Azure/sonic-route-map";
    prefix srmap;
    yang-version 1.1;

    import ietf-yang-types {
        prefix yang;
    }

    import ietf-inet-types {
        prefix inet;
    }

    import sonic-port {
        prefix prt;
    }

    import sonic-portchannel {
        prefix spc;
    }

    import sonic-routing-policy-sets {
        prefix srpolsets;
    }

    import sonic-vlan {
        prefix svlan;
    }

    organization
        "SONiC";

    contact
        "SONiC";

    description
        "SONIC Route map YANG";

    revision 2019-09-15 {
        description
            "Initial revision.";
    }

    typedef tag-type {
        type union {
            type uint32;
            type yang:hex-string;
        }
        description "type for expressing route tags on a local system,
                    including IS-IS and OSPF; may be expressed as either decimal or
                        hexidecimal integer";
        reference
            "RFC 2178 OSPF Version 2
            RFC 5130 A Policy Control Mechanism in IS-IS Using
            Administrative Tags";
    }

    typedef route-map-intf {
        type union {
            type leafref {
                path "/prt:sonic-port/prt:PORT/prt:PORT_LIST/prt:ifname";
            }
            type leafref {
                path "/spc:sonic-portchannel/spc:PORTCHANNEL/spc:PORTCHANNEL_LIST/spc:name";
            }
            type leafref {
                path "/svlan:sonic-vlan/svlan:VLAN/svlan:VLAN_LIST/svlan:name";
            }
        }
    }

    typedef bgp-origin-attr-type {
        type enumeration {
            enum IGP {
                description
                "Origin of the NLRI is internal";
            }
            enum EGP {
                description
                "Origin of the NLRI is EGP";
            }
            enum INCOMPLETE {
                description
                "Origin of the NLRI is neither IGP or EGP";
            }
        }
        description
            "Type definition for standard BGP origin attribute";
              reference "RFC 4271 - A Border Gateway Protocol 4 (BGP-4),
              Sec 4.3";
    }

    typedef bgp-set-med-type {
        type union {
            type uint32;
            type string {
                pattern '^[+-][0-9]+$';
            }
            type enumeration {
                enum IGP {
                   description "set the MED value to the IGP cost toward the next hop for the route";
                }
            }
        }
        description
                   "Type definition for specifying how the BGP MED can
                    be set in BGP policy actions. The three choices are to set
                    the MED directly, increment/decrement using +/- notation,
                    and setting it to the IGP cost (predefined value).";
    }

    container sonic-route-map {
        container ROUTE_MAP_SET {
            list ROUTE_MAP_SET_LIST {
                key "name";

                leaf name {
                    type string;
                }
            }
        }

        container ROUTE_MAP {
            list ROUTE_MAP_LIST {
                key "route_map_name stmt_name";

                leaf route_map_name {
                    type string;
                }

                leaf stmt_name {
                    type uint16 {
                        range 1..65535;
                    }
                }

                leaf route_operation {
                    type string;
                }

                leaf match_interface{
                    type route-map-intf;
                }

                leaf match_prefix_set{
                    type leafref {
                        path "/srpolsets:sonic-routing-policy-sets/srpolsets:PREFIX_SET/srpolsets:PREFIX_SET_LIST/srpolsets:name";
                    }
                }

                leaf match_protocol {
                    type string;
                }

                leaf match_next_hop_set {
                    type leafref {
                        path "/srpolsets:sonic-routing-policy-sets/srpolsets:PREFIX_SET/srpolsets:PREFIX_SET_LIST/srpolsets:name";
                    }
                }

                leaf-list match_neighbor {
                    type union {
                        type inet:ip-address;
                        type leafref {
                            path "/prt:sonic-port/prt:PORT/prt:PORT_LIST/prt:ifname";
                        }
                        type leafref {
                            path "/spc:sonic-portchannel/spc:PORTCHANNEL/spc:PORTCHANNEL_LIST/spc:name";
                        }
                        type leafref {
                            path "/svlan:sonic-vlan/svlan:VLAN/svlan:VLAN_LIST/svlan:name";
                        }
                    }
                    description
                        "IP addresse or interface for match operation.";
                    must "(count(current()) = 1)" {
                        error-app-tag "max-allowed-neighbor-reached";
                        error-message "Only one neighbor or interface can be configured.";
                    }
                }

                leaf-list match_tag {
                    type tag-type;
                    description
                        "Value of the tag match member";
                    must "(count(current()) = 1)" {
                        error-app-tag "max-allowed-tag-reached";
                        error-message "Only one tag value can be configured.";
                    }
                }

                leaf match_med{
                    type uint32;
                }

                leaf match_origin{
                    type string;
                }

                leaf match_local_pref{
                    type uint32;
                }

                leaf match_community{
                    type leafref {
                        path "/srpolsets:sonic-routing-policy-sets/srpolsets:COMMUNITY_SET/srpolsets:COMMUNITY_SET_LIST/srpolsets:name";
                    }
                }

                leaf match_ext_community{
                    type leafref {
                        path "/srpolsets:sonic-routing-policy-sets/srpolsets:EXTENDED_COMMUNITY_SET/srpolsets:EXTENDED_COMMUNITY_SET_LIST/srpolsets:name";
                    }
                }

                leaf match_as_path{
                    type leafref {
                        path "/srpolsets:sonic-routing-policy-sets/srpolsets:AS_PATH_SET/srpolsets:AS_PATH_SET_LIST/srpolsets:name";
                    }
                }
                leaf call_route_map {
                    type leafref {
                        path "../../../ROUTE_MAP_SET/ROUTE_MAP_SET_LIST/name";
                    }
                }

                leaf set_origin{
                    type string;
                }

                leaf set_local_pref{
                    type uint32;
                }

                leaf set_med {
                    type bgp-set-med-type;
                }

                leaf set_next_hop{
                    type string;
                }
                 
                leaf set_repeat_asn{
                    type uint8;
                }

                leaf set_asn{
                    type uint32;
                }
 
                leaf set_asn_list{
                    type string;
                }

                leaf-list set_community_inline {
                    type string;
                }

                leaf set_community_ref {
                    type leafref {
                        path "/srpolsets:sonic-routing-policy-sets/srpolsets:COMMUNITY_SET/srpolsets:COMMUNITY_SET_LIST/srpolsets:name";
                    }
                }

                leaf-list set_ext_community_inline {
                    type string;
                }

                leaf set_ext_community_ref {
                    type leafref {
                        path "/srpolsets:sonic-routing-policy-sets/srpolsets:EXTENDED_COMMUNITY_SET/srpolsets:EXTENDED_COMMUNITY_SET_LIST/srpolsets:name";
                    }
                }

                leaf set_tag {
                    type tag-type;
                    description
                        "Value of the tag set member";
                }

                leaf set_weight{
                    type uint32;
                }

            }
        }
    }
}
