module openfabric-endpoint-service {
    yang-version 1;
    namespace "com:att:sdnctl:openfabric-endpoint-service:v1";
    prefix "ofes";
    import openfabric-types { prefix oft; revision-date "2017-11-21"; }
    import openfabric-endpoint-data { prefix ofed; revision-date "2019-04-29"; }
    import openfabric-underlay-data { prefix ofud; revision-date "2019-04-29"; }
    import nextgendc-rbac { prefix nrbac; revision-date "2018-04-19"; }

    description "Module stores information about devices connected in datacenter. Provides rpcs for configuring ports
    according to specified templates, list endpoints etc.";

    revision "2019-04-29" {
        description "Initial revision of openfabric endpoints model";
    }

    grouping ipam-stats {
        leaf missing-in-ipam-count {
            type uint32;
        }
        leaf missing-in-odl-count {
          type uint32;
        }
        leaf in-draft-count {
          type uint32;
        }
        leaf in-sync-count {
          type uint32;
        }
        leaf out-of-sync-count {
          type uint32;
        }
    }

    grouping ipam-vlan {
        leaf vid {
            type uint16;
        }
        leaf name {
            type string;
        }
        leaf vlan-group {
            type string;
        }
    }

    grouping ipam-endpoint {
        leaf logical-endpoint {
            type string;
        }
        list intended-vlans {
            key vid;
            uses ipam-vlan;
        }
        leaf connection-type {
            type enumeration {
                enum sp;
                enum dpc;
                enum vpc;
            }
        }
        leaf device-type {
            type string;
        }
        leaf tenant {
            type string;
        }
        list physical-interfaces {
            leaf name {
                type string;
            }
            leaf port-name {
                type string;
            }
            leaf device-name {
                type string;
            }
        }
        container vlan-collection {
            leaf name {
                type string;
            }
            container native-vlan {
                uses ipam-vlan;
            }
            leaf mode {
                type string;
            }
        }
    }

    grouping ipam-endpoint-diff {
        leaf endpoint-name {
            type string;
        }
        leaf state {
            type enumeration {
                enum in-sync;
                enum in-draft;
                enum out-of-sync;
                enum missing-in-ipam;
                enum missing-in-odl;
            }
        }
        list diff {
            key id;
            leaf id {
                type string;
            }
            leaf ipam {
                type string;
            }
            leaf odl {
                type string;
            }
        }
        container ipam {
            uses ipam-endpoint;
        }
        container odl {
            uses ipam-endpoint;
        }
    }

    rpc get-endpoint-templates {
        description "Lists all available templates for provided device type";
        nrbac:required-rpc-permission "openfabric::read";
        input {
            uses nrbac:permissions-object;
            leaf device-type {
                description "Device type.";
                type oft:device-type-enum;
                mandatory true;
            }
        }
        output {
            leaf-list templates {
                description "Template list for given device type.";
                type string;
            }
        }
    }

    rpc create-endpoint {
        description "Creates endpoint on specified ports according to template.";
        nrbac:required-rpc-permission "openfabric::edit";
        nrbac:required-instance-permission "openfabric:/owner:edit";
        input {
            uses oft:auth;
            uses ofud:pod-identifier;
            uses ofed:endpoint-fields;
            uses oft:force;
        }
        output {
            uses oft:device-operation-result;
        }
    }

    rpc edit-endpoint {
        description "Edits endpoint on specified ports according to template.";
        nrbac:required-rpc-permission "openfabric::edit";
        nrbac:required-instance-permission "openfabric:/owner:edit";
        input {
            uses oft:auth;
            uses ofud:pod-identifier;
            uses ofed:endpoint-fields;
            uses oft:force;
        }
        output {
            uses oft:device-operation-result;
        }
    }

    rpc remove-endpoint {
        status deprecated;
        description "Deprecated. Use remove-endpoints instead. Detaches endpoint from all its vlans and then deletes it.";
        nrbac:required-rpc-permission "openfabric::edit";
        input {
            uses oft:auth;
            uses ofud:pod-identifier;
            leaf name {
                description "Endpoint name";
                type oft:endpoint-name;
                mandatory true;
            }
        }
        output {
            uses oft:device-operation-result;
        }
    }

    rpc remove-endpoints {
        description "Detaches endpoint from all its vlans and then deletes it.";
        nrbac:required-rpc-permission "openfabric::edit";
        input {
            uses oft:auth;
            uses ofud:pod-identifier;
            leaf-list endpoints {
                description "Endpoint name";
                type oft:endpoint-name;
            }
            uses oft:force;
        }
        output {
            uses oft:device-operation-result;
        }
    }

    rpc set-endpoint-vlans {
        description "Assigns vlans to endpoint as specified in input";
        nrbac:required-rpc-permission "openfabric::edit";
        input {
            uses oft:auth;
            uses ofud:pod-identifier;
            leaf name {
                description "Endpoint name";
                type oft:endpoint-name;
                mandatory true;
            }
            list tenant {
                uses ofed:endpoint-tenant;
                list vlan {
                    uses ofed:endpoint-vlan;
                }
            }
            uses oft:force;
        }
        output {
            uses oft:device-operation-result;
        }
    }

    rpc get-endpoints {
        description "Returns list of pod endpoints.";
        nrbac:required-rpc-permission "openfabric::read";
        input {
            uses nrbac:permissions-object;
            uses ofud:pod-identifier;
        }
        output {
            list endpoint {
                uses ofed:endpoint-fields;
                uses oft:config-status;
                list tenant {
                    uses ofed:endpoint-tenant;
                    list vlan {
                        uses ofed:endpoint-vlan;
                    }
                }
            }
        }
    }

    rpc get-ipam-endpoint-diff {
        description "Returns list of pod endpoints.";
        nrbac:required-rpc-permission "openfabric::read";
        input {
            uses nrbac:permissions-object;
            uses ofud:pod-identifier;
            leaf endpoint {
                description "Endpoint name";
                type oft:endpoint-name;
                mandatory true;
            }
        }
        output {
            uses ipam-stats;
            container endpoint-diff {
                uses ipam-endpoint-diff;
            }
        }
    }

    rpc get-ipam-endpoints-diff {
        description "Returns list of pod endpoints.";
        nrbac:required-rpc-permission "openfabric::read";
        input {
            uses nrbac:permissions-object;
            uses ofud:pod-identifier;
        }
        output {
            uses ipam-stats;
            list endpoint-diff {
                key endpoint-name;
                uses ipam-endpoint-diff;
            }
        }
    }

    rpc import-port-profiles-from-csv {
        description "Import endpoints from CSV format.";
        nrbac:required-rpc-permission "openfabric::edit";
        input {
            uses oft:auth;
            uses ofud:pod-identifier;
            leaf csv {
                description "Csv describing endpoint with columns
                    NAME,CONNECTION_TYPE,CONNECTION_MODE,DEVICE_TYPE,IFACE_SPEED,DESCRIPTION,SWITCHES,PORTS,TEMPLATE";
                type string;
                mandatory true;
            }
            uses oft:force;
        }
        output {
            uses oft:device-operation-result;
        }
    }

    rpc export-port-profiles-to-csv {
        description "Export existing endpoints to CSV format.";
        nrbac:required-rpc-permission "openfabric::read";
        input {
            uses nrbac:permissions-object;
            uses ofud:pod-identifier;
        }
        output {
            leaf csv {
                description "Csv describing endpoint with columns
                    NAME,CONNECTION_TYPE,CONNECTION_MODE,DEVICE_TYPE,IFACE_SPEED,DESCRIPTION,SWITCHES,PORTS,TEMPLATE";
                type string;
            }
        }
    }

}
